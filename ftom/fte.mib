FTE-E	 DEFINITIONS ::= BEGIN
       IMPORTS
       Integer32, OBJECT-TYPE, MODULE-IDENTITY,
       enterprises
          FROM SNMPv2-SMI
       DisplayString
          FROM SNMPv2-TC
        OBJECT-GROUP
          FROM SNMPv2-CONF;
        MacAddress ::= OCTET STRING
        IPAddress ::= OCTET STRING

        futuretek       OBJECT IDENTIFIER ::= { enterprises 42251 }

        fte             OBJECT IDENTIFIER ::= { futuretek 1 }

        product         OBJECT IDENTIFIER ::= { fte 1 }

        network         OBJECT IDENTIFIER ::= { fte 2 }

        endpoints       OBJECT IDENTIFIER ::= { fte 3 }

        servers         OBJECT IDENTIFIER ::= { fte 5 }

        logs            OBJECT IDENTIFIER ::= { fte 6 }

        power           OBJECT IDENTIFIER ::= { fte 7 }

        events          OBJECT IDENTIFIER ::= { fte 8 }

        traps           OBJECT IDENTIFIER ::= { fte 100 }

        admin           OBJECT IDENTIFIER ::= { fte 65535 }

        epTemperature   OBJECT IDENTIFIER ::= { endpoints 256 }

        epHumidity      OBJECT IDENTIFIER ::= { endpoints 512 }

        epVoltage       OBJECT IDENTIFIER ::= { endpoints 768 }

        epCurrent       OBJECT IDENTIFIER ::= { endpoints 1024 }

        epDI            OBJECT IDENTIFIER ::= { endpoints 1280 }

        epDO            OBJECT IDENTIFIER ::= { endpoints 1536 }

        epGAS           OBJECT IDENTIFIER ::= { endpoints 1792 }

        epPower         OBJECT IDENTIFIER ::= { endpoints 2048 }

        epCount         OBJECT IDENTIFIER ::= { endpoints 2816 }

        epPressure      OBJECT IDENTIFIER ::= { endpoints 3072 }

        epDiscrete      OBJECT IDENTIFIER ::= { endpoints 3328 }

        epMulti         OBJECT IDENTIFIER ::= { endpoints 32256 }
        
        epCtrl			OBJECT IDENTIFIER ::= { endpoints 32512 }

        epMgmt          OBJECT IDENTIFIER ::= { endpoints 65535 }

        netType OBJECT-TYPE
                SYNTAX INTEGER
                ACCESS read-only
                STATUS mandatory
                DESCRIPTION
                        ""
                ::= { network 1 }

        netMacAddr OBJECT-TYPE
                SYNTAX MacAddress
                ACCESS read-only
                STATUS mandatory
                DESCRIPTION
                        ""
                ::= { network 2 }

        netIpAddr OBJECT-TYPE
                SYNTAX IPAddress
                ACCESS read-only
                STATUS mandatory
                DESCRIPTION
                        ""
                ::= { network 3 }

        netNetMask OBJECT-TYPE
                SYNTAX IPAddress
                ACCESS read-only
                STATUS mandatory
                DESCRIPTION
                        ""
                ::= { network 4 }

        netGateway OBJECT-TYPE
                SYNTAX IPAddress
                ACCESS read-only
                STATUS mandatory
                DESCRIPTION
                        ""
                ::= { network 5 }

        prodID OBJECT-TYPE
                SYNTAX DisplayString
                ACCESS read-only
                STATUS mandatory
                DESCRIPTION
                        ""
                ::= { product 1 }

        prodModel OBJECT-TYPE
                SYNTAX DisplayString
                ACCESS read-only
                STATUS mandatory
                DESCRIPTION
                        ""
                ::= { product 2 }

        prodVendor OBJECT-TYPE
                SYNTAX DisplayString
                ACCESS read-only
                STATUS mandatory
                DESCRIPTION
                        ""
                ::= { product 3 }

        prodHWVer OBJECT-TYPE
                SYNTAX DisplayString
                ACCESS read-only
                STATUS mandatory
                DESCRIPTION
                        ""
                ::= { product 4 }

        prodSWVer OBJECT-TYPE
                SYNTAX DisplayString
                ACCESS read-only
                STATUS mandatory
                DESCRIPTION
                        ""
                ::= { product 5 }

        prodDesc OBJECT-TYPE
                SYNTAX DisplayString
                ACCESS read-write
                STATUS mandatory
                DESCRIPTION
                        ""
                ::= { product 6 }

        tempCount OBJECT-TYPE
                SYNTAX INTEGER
                ACCESS read-only
                STATUS mandatory
                DESCRIPTION
                        ""
                ::= { epTemperature 1 }

        tempTable OBJECT-TYPE
                SYNTAX SEQUENCE OF TempEntry
                ACCESS not-accessible
                STATUS deprecated
                DESCRIPTION
                        ""
                ::= { epTemperature 2 }

        tempEntry OBJECT-TYPE
                SYNTAX TempEntry
                ACCESS not-accessible
                STATUS deprecated
                DESCRIPTION
                        ""
                INDEX { tempID }
                ::= { tempTable 1 }

        TempEntry ::= SEQUENCE { 
            tempID DisplayString,
            tempType DisplayString,
            tempName DisplayString,
            tempSN DisplayString,
            tempState DisplayString,
            tempValue DisplayString,
            tempLastValue DisplayString,
            tempLastTime DisplayString,
            tempUpdateInterval INTEGER
        }

        tempID OBJECT-TYPE
                SYNTAX DisplayString
                ACCESS read-only
                STATUS deprecated
                DESCRIPTION
                        ""
                ::= { tempEntry 1 }

        tempType OBJECT-TYPE
                SYNTAX DisplayString
                ACCESS read-only
                STATUS deprecated
                DESCRIPTION
                        ""
                ::= { tempEntry 2 }

        tempName OBJECT-TYPE
                SYNTAX DisplayString
                ACCESS read-write
                STATUS deprecated
                DESCRIPTION
                        ""
                ::= { tempEntry 3 }

        tempSN OBJECT-TYPE
                SYNTAX DisplayString
                ACCESS read-only
                STATUS deprecated
                DESCRIPTION
                        ""
                ::= { tempEntry 4 }

        tempState OBJECT-TYPE
                SYNTAX DisplayString
                ACCESS read-write
                STATUS deprecated
                DESCRIPTION
                        ""
                ::= { tempEntry 5 }

        tempValue OBJECT-TYPE
                SYNTAX DisplayString
                ACCESS read-only
                STATUS deprecated
                DESCRIPTION
                        ""
                ::= { tempEntry 6 }

        tempLastValue OBJECT-TYPE
                SYNTAX DisplayString
                ACCESS read-only
                STATUS deprecated
                DESCRIPTION
                        ""
                ::= { tempEntry 7 }

        tempLastTime OBJECT-TYPE
                SYNTAX DisplayString
                ACCESS read-only
                STATUS deprecated
                DESCRIPTION
                        ""
                ::= { tempEntry 8 }

        tempUpdateInterval OBJECT-TYPE
                SYNTAX INTEGER
                ACCESS read-write
                STATUS mandatory
                DESCRIPTION
                        ""
                ::= { tempEntry 9 }

        humiCount OBJECT-TYPE
                SYNTAX INTEGER
                ACCESS read-only
                STATUS mandatory
                DESCRIPTION
                        ""
                ::= { epHumidity 1 }

        humiTable OBJECT-TYPE
                SYNTAX SEQUENCE OF HumiEntry
                ACCESS not-accessible
                STATUS deprecated
                DESCRIPTION
                        ""
                ::= { epHumidity 2 }

        humiEntry OBJECT-TYPE
                SYNTAX HumiEntry
                ACCESS not-accessible
                STATUS deprecated
                DESCRIPTION
                        ""
                INDEX { humiID }
                ::= { humiTable 1 }

        HumiEntry ::= SEQUENCE { 
            humiID DisplayString,
            humiType DisplayString,
            humiName DisplayString,
            humiSN DisplayString,
            humiState DisplayString,
            humiValue DisplayString,
            humiLastValue DisplayString,
            humiLastTime DisplayString,
            humiUpdateInterval INTEGER
        }

        humiID OBJECT-TYPE
                SYNTAX DisplayString
                ACCESS read-only
                STATUS deprecated
                DESCRIPTION
                        ""
                ::= { humiEntry 1 }

        humiType OBJECT-TYPE
                SYNTAX DisplayString
                ACCESS read-only
                STATUS deprecated
                DESCRIPTION
                        ""
                ::= { humiEntry 2 }

        humiName OBJECT-TYPE
                SYNTAX DisplayString
                ACCESS read-write
                STATUS deprecated
                DESCRIPTION
                        ""
                ::= { humiEntry 3 }

        humiSN OBJECT-TYPE
                SYNTAX DisplayString
                ACCESS read-only
                STATUS deprecated
                DESCRIPTION
                        ""
                ::= { humiEntry 4 }

        humiState OBJECT-TYPE
                SYNTAX DisplayString
                ACCESS read-write
                STATUS deprecated
                DESCRIPTION
                        ""
                ::= { humiEntry 5 }

        humiValue OBJECT-TYPE
                SYNTAX DisplayString
                ACCESS read-only
                STATUS deprecated
                DESCRIPTION
                        ""
                ::= { humiEntry 6 }

        humiLastValue OBJECT-TYPE
                SYNTAX DisplayString
                ACCESS read-only
                STATUS deprecated
                DESCRIPTION
                        ""
                ::= { humiEntry 7 }

        humiLastTime OBJECT-TYPE
                SYNTAX DisplayString
                ACCESS read-only
                STATUS deprecated
                DESCRIPTION
                        ""
                ::= { humiEntry 8 }

        humiUpdateInterval OBJECT-TYPE
                SYNTAX INTEGER
                ACCESS read-write
                STATUS mandatory
                DESCRIPTION
                        ""
                ::= { humiEntry 9 }

        vltCount OBJECT-TYPE
                SYNTAX INTEGER
                ACCESS read-only
                STATUS mandatory
                DESCRIPTION
                        ""
                ::= { epVoltage 1 }

        vltTable OBJECT-TYPE
                SYNTAX SEQUENCE OF VltEntry
                ACCESS not-accessible
                STATUS deprecated
                DESCRIPTION
                        ""
                ::= { epVoltage 2 }

        vltEntry OBJECT-TYPE
                SYNTAX VltEntry
                ACCESS not-accessible
                STATUS deprecated
                DESCRIPTION
                        ""
                INDEX { vltID }
                ::= { vltTable 1 }

        VltEntry ::= SEQUENCE { 
            vltID DisplayString,
            vltType DisplayString,
            vltName DisplayString,
            vltSN DisplayString,
            vltState DisplayString,
            vltValue DisplayString,
            vltLastValue DisplayString,
            vltLastTime DisplayString,
            vltUpdateInterval INTEGER
        }

        vltID OBJECT-TYPE
                SYNTAX DisplayString
                ACCESS read-only
                STATUS deprecated
                DESCRIPTION
                        ""
                ::= { vltEntry 1 }

        vltType OBJECT-TYPE
                SYNTAX DisplayString
                ACCESS read-only
                STATUS deprecated
                DESCRIPTION
                        ""
                ::= { vltEntry 2 }

        vltName OBJECT-TYPE
                SYNTAX DisplayString
                ACCESS read-write
                STATUS deprecated
                DESCRIPTION
                        ""
                ::= { vltEntry 3 }

        vltSN OBJECT-TYPE
                SYNTAX DisplayString
                ACCESS read-only
                STATUS deprecated
                DESCRIPTION
                        ""
                ::= { vltEntry 4 }

        vltState OBJECT-TYPE
                SYNTAX DisplayString
                ACCESS read-write
                STATUS deprecated
                DESCRIPTION
                        ""
                ::= { vltEntry 5 }

        vltValue OBJECT-TYPE
                SYNTAX DisplayString
                ACCESS read-only
                STATUS deprecated
                DESCRIPTION
                        ""
                ::= { vltEntry 6 }

        vltLastValue OBJECT-TYPE
                SYNTAX DisplayString
                ACCESS read-only
                STATUS deprecated
                DESCRIPTION
                        ""
                ::= { vltEntry 7 }

        vltLastTime OBJECT-TYPE
                SYNTAX DisplayString
                ACCESS read-only
                STATUS deprecated
                DESCRIPTION
                        ""
                ::= { vltEntry 8 }

        vltUpdateInterval OBJECT-TYPE
                SYNTAX INTEGER
                ACCESS read-write
                STATUS deprecated
                DESCRIPTION
                        ""
                ::= { vltEntry 9 }

        currCount OBJECT-TYPE
                SYNTAX INTEGER
                ACCESS read-only
                STATUS mandatory
                DESCRIPTION
                        ""
                ::= { epCurrent 1 }

        currTable OBJECT-TYPE
                SYNTAX SEQUENCE OF CurrEntry
                ACCESS not-accessible
                STATUS deprecated
                DESCRIPTION
                        ""
                ::= { epCurrent 2 }

        currEntry OBJECT-TYPE
                SYNTAX CurrEntry
                ACCESS not-accessible
                STATUS deprecated
                DESCRIPTION
                        ""
                INDEX { currID }
                ::= { currTable 1 }

        CurrEntry ::= SEQUENCE { 
            currID DisplayString,
            currType DisplayString,
            currName DisplayString,
            currSN DisplayString,
            currState DisplayString,
            currValue DisplayString,
            currLastValue DisplayString,
            currLastTime DisplayString,
            currUpdateInterval INTEGER
        }

        currID OBJECT-TYPE
                SYNTAX DisplayString
                ACCESS read-only
                STATUS deprecated
                DESCRIPTION
                        ""
                ::= { currEntry 1 }

        currType OBJECT-TYPE
                SYNTAX DisplayString
                ACCESS read-only
                STATUS deprecated
                DESCRIPTION
                        ""
                ::= { currEntry 2 }

        currName OBJECT-TYPE
                SYNTAX DisplayString
                ACCESS read-write
                STATUS deprecated
                DESCRIPTION
                        ""
                ::= { currEntry 3 }

        currSN OBJECT-TYPE
                SYNTAX DisplayString
                ACCESS read-only
                STATUS deprecated
                DESCRIPTION
                        ""
                ::= { currEntry 4 }

        currState OBJECT-TYPE
                SYNTAX DisplayString
                ACCESS read-write
                STATUS deprecated
                DESCRIPTION
                        ""
                ::= { currEntry 5 }

        currValue OBJECT-TYPE
                SYNTAX DisplayString
                ACCESS read-only
                STATUS deprecated
                DESCRIPTION
                        ""
                ::= { currEntry 6 }

        currLastValue OBJECT-TYPE
                SYNTAX DisplayString
                ACCESS read-only
                STATUS deprecated
                DESCRIPTION
                        ""
                ::= { currEntry 7 }

        currLastTime OBJECT-TYPE
                SYNTAX DisplayString
                ACCESS read-only
                STATUS deprecated
                DESCRIPTION
                        ""
                ::= { currEntry 8 }

        currUpdateInterval OBJECT-TYPE
                SYNTAX INTEGER
                ACCESS read-write
                STATUS deprecated
                DESCRIPTION
                        ""
                ::= { currEntry 9 }

        diCount OBJECT-TYPE
                SYNTAX INTEGER
                ACCESS read-only
                STATUS mandatory
                DESCRIPTION
                        ""
                ::= { epDI 1 }

        diTable OBJECT-TYPE
                SYNTAX SEQUENCE OF DiEntry
                ACCESS not-accessible
                STATUS deprecated
                DESCRIPTION
                        ""
                ::= { epDI 2 }

        diEntry OBJECT-TYPE
                SYNTAX DiEntry
                ACCESS not-accessible
                STATUS deprecated
                DESCRIPTION
                        ""
                INDEX { diID }
                ::= { diTable 1 }

        DiEntry ::= SEQUENCE { 
            diID DisplayString,
            diType DisplayString,
            diName DisplayString,
            diSN DisplayString,
            diState DisplayString,
            diValue DisplayString,
            diLastValue DisplayString,
            diLastTime DisplayString,
            diUpdateInterval INTEGER
        }

        diID OBJECT-TYPE
                SYNTAX DisplayString
                ACCESS read-only
                STATUS deprecated
                DESCRIPTION
                        ""
                ::= { diEntry 1 }

        diType OBJECT-TYPE
                SYNTAX DisplayString
                ACCESS read-only
                STATUS deprecated
                DESCRIPTION
                        ""
                ::= { diEntry 2 }

        diName OBJECT-TYPE
                SYNTAX DisplayString
                ACCESS read-write
                STATUS deprecated
                DESCRIPTION
                        ""
                ::= { diEntry 3 }

        diSN OBJECT-TYPE
                SYNTAX DisplayString
                ACCESS read-only
                STATUS deprecated
                DESCRIPTION
                        ""
                ::= { diEntry 4 }

        diState OBJECT-TYPE
                SYNTAX DisplayString
                ACCESS read-write
                STATUS deprecated
                DESCRIPTION
                        ""
                ::= { diEntry 5 }

        diValue OBJECT-TYPE
                SYNTAX DisplayString
                ACCESS read-only
                STATUS deprecated
                DESCRIPTION
                        ""
                ::= { diEntry 6 }

        diLastValue OBJECT-TYPE
                SYNTAX DisplayString
                ACCESS read-only
                STATUS deprecated
                DESCRIPTION
                        ""
                ::= { diEntry 7 }

        diLastTime OBJECT-TYPE
                SYNTAX DisplayString
                ACCESS read-only
                STATUS deprecated
                DESCRIPTION
                        ""
                ::= { diEntry 8 }

        diUpdateInterval OBJECT-TYPE
                SYNTAX INTEGER
                ACCESS read-write
                STATUS deprecated
                DESCRIPTION
                        ""
                ::= { diEntry 9 }

        doCount OBJECT-TYPE
                SYNTAX INTEGER
                ACCESS read-only
                STATUS mandatory
                DESCRIPTION
                        ""
                ::= { epDO 1 }

        doTable OBJECT-TYPE
                SYNTAX SEQUENCE OF DoEntry
                ACCESS not-accessible
                STATUS deprecated
                DESCRIPTION
                        ""
                ::= { epDO 2 }

        doEntry OBJECT-TYPE
                SYNTAX DoEntry
                ACCESS not-accessible
                STATUS deprecated
                DESCRIPTION
                        ""
                INDEX { doID }
                ::= { doTable 1 }

        DoEntry ::= SEQUENCE { 
            doID DisplayString,
            doType DisplayString,
            doName DisplayString,
            doSN DisplayString,
            doState DisplayString,
            doValue DisplayString,
            doLastValue DisplayString,
            doLastTime DisplayString,
            doInitValue DisplayString
        }

        doID OBJECT-TYPE
                SYNTAX DisplayString
                ACCESS read-only
                STATUS deprecated
                DESCRIPTION
                        ""
                ::= { doEntry 1 }

        doType OBJECT-TYPE
                SYNTAX DisplayString
                ACCESS read-only
                STATUS deprecated
                DESCRIPTION
                        ""
                ::= { doEntry 2 }

        doName OBJECT-TYPE
                SYNTAX DisplayString
                ACCESS read-write
                STATUS deprecated
                DESCRIPTION
                        ""
                ::= { doEntry 3 }

        doSN OBJECT-TYPE
                SYNTAX DisplayString
                ACCESS read-only
                STATUS deprecated
                DESCRIPTION
                        ""
                ::= { doEntry 4 }

        doState OBJECT-TYPE
                SYNTAX DisplayString
                ACCESS read-write
                STATUS deprecated
                DESCRIPTION
                        ""
                ::= { doEntry 5 }

        doValue OBJECT-TYPE
                SYNTAX DisplayString
                ACCESS read-write
                STATUS deprecated
                DESCRIPTION
                        ""
                ::= { doEntry 6 }

        doLastValue OBJECT-TYPE
                SYNTAX DisplayString
                ACCESS read-only
                STATUS deprecated
                DESCRIPTION
                        ""
                ::= { doEntry 7 }

        doLastTime OBJECT-TYPE
                SYNTAX DisplayString
                ACCESS read-only
                STATUS deprecated
                DESCRIPTION
                        ""
                ::= { doEntry 8 }

        doInitValue OBJECT-TYPE
                SYNTAX DisplayString
                ACCESS read-write
                STATUS deprecated
                DESCRIPTION
                        ""
                ::= { doEntry 9 }

        pwrCount OBJECT-TYPE
                SYNTAX INTEGER
                ACCESS read-only
                STATUS mandatory
                DESCRIPTION
                        ""
                ::= { epPower 1 }

        pwrTable OBJECT-TYPE
                SYNTAX SEQUENCE OF PwrEntry
                ACCESS not-accessible
                STATUS deprecated
                DESCRIPTION
                        ""
                ::= { epPower 2 }

        pwrEntry OBJECT-TYPE
                SYNTAX PwrEntry
                ACCESS not-accessible
                STATUS deprecated
                DESCRIPTION
                        ""
                INDEX { gasID }
                ::= { pwrTable 1 }

        PwrEntry ::= SEQUENCE { 
            pwrID DisplayString,
            pwrType DisplayString,
            pwrName DisplayString,
            pwrSN DisplayString,
            pwrState DisplayString,
            pwrValue DisplayString,
            pwrLastValue DisplayString,
            pwrLastTime DisplayString,
            pwrUpdateInterval INTEGER
        }

        pwrID OBJECT-TYPE
                SYNTAX DisplayString
                ACCESS read-only
                STATUS deprecated
                DESCRIPTION
                        ""
                ::= { pwrEntry 1 }

        pwrType OBJECT-TYPE
                SYNTAX DisplayString
                ACCESS read-only
                STATUS deprecated
                DESCRIPTION
                        ""
                ::= { pwrEntry 2 }

        pwrName OBJECT-TYPE
                SYNTAX DisplayString
                ACCESS read-write
                STATUS deprecated
                DESCRIPTION
                        ""
                ::= { pwrEntry 3 }

        pwrSN OBJECT-TYPE
                SYNTAX DisplayString
                ACCESS read-only
                STATUS deprecated
                DESCRIPTION
                        ""
                ::= { pwrEntry 4 }

        pwrState OBJECT-TYPE
                SYNTAX DisplayString
                ACCESS read-write
                STATUS deprecated
                DESCRIPTION
                        ""
                ::= { pwrEntry 5 }

        pwrValue OBJECT-TYPE
                SYNTAX DisplayString
                ACCESS read-only
                STATUS deprecated
                DESCRIPTION
                        ""
                ::= { pwrEntry 6 }

        pwrLastValue OBJECT-TYPE
                SYNTAX DisplayString
                ACCESS read-only
                STATUS deprecated
                DESCRIPTION
                        ""
                ::= { pwrEntry 7 }

        pwrLastTime OBJECT-TYPE
                SYNTAX DisplayString
                ACCESS read-only
                STATUS deprecated
                DESCRIPTION
                        ""
                ::= { pwrEntry 8 }

        pwrUpdateInterval OBJECT-TYPE
                SYNTAX INTEGER
                ACCESS read-write
                STATUS mandatory
                DESCRIPTION
                        ""
                ::= { pwrEntry 9 }

        gasCount OBJECT-TYPE
                SYNTAX INTEGER
                ACCESS read-only
                STATUS mandatory
                DESCRIPTION
                        ""
                ::= { epGAS 1 }

        gasTable OBJECT-TYPE
                SYNTAX SEQUENCE OF GasEntry
                ACCESS not-accessible
                STATUS deprecated
                DESCRIPTION
                        ""
                ::= { epGAS 2 }

        gasEntry OBJECT-TYPE
                SYNTAX GasEntry
                ACCESS not-accessible
                STATUS deprecated
                DESCRIPTION
                        ""
                INDEX { gasID }
                ::= { gasTable 1 }

        GasEntry ::= SEQUENCE { 
            gasID DisplayString,
            gasType DisplayString,
            gasName DisplayString,
            gasSN DisplayString,
            gasState DisplayString,
            gasValue DisplayString,
            gasLastValue DisplayString,
            gasLastTime DisplayString,
            gasUpdateInterval INTEGER,
            gasTotalTrial INTEGER,
            gasTotalFailed INTEGER
        }

        gasID OBJECT-TYPE
                SYNTAX DisplayString
                ACCESS read-only
                STATUS deprecated
                DESCRIPTION
                        ""
                ::= { gasEntry 1 }

        gasType OBJECT-TYPE
                SYNTAX DisplayString
                ACCESS read-only
                STATUS deprecated
                DESCRIPTION
                        ""
                ::= { gasEntry 2 }

        gasName OBJECT-TYPE
                SYNTAX DisplayString
                ACCESS read-write
                STATUS deprecated
                DESCRIPTION
                        ""
                ::= { gasEntry 3 }

        gasSN OBJECT-TYPE
                SYNTAX DisplayString
                ACCESS read-only
                STATUS deprecated
                DESCRIPTION
                        ""
                ::= { gasEntry 4 }

        gasState OBJECT-TYPE
                SYNTAX DisplayString
                ACCESS read-write
                STATUS deprecated
                DESCRIPTION
                        ""
                ::= { gasEntry 5 }

        gasValue OBJECT-TYPE
                SYNTAX DisplayString
                ACCESS read-only
                STATUS deprecated
                DESCRIPTION
                        ""
                ::= { gasEntry 6 }

        gasLastValue OBJECT-TYPE
                SYNTAX DisplayString
                ACCESS read-only
                STATUS deprecated
                DESCRIPTION
                        ""
                ::= { gasEntry 7 }

        gasLastTime OBJECT-TYPE
                SYNTAX DisplayString
                ACCESS read-only
                STATUS deprecated
                DESCRIPTION
                        ""
                ::= { gasEntry 8 }

        gasUpdateInterval OBJECT-TYPE
                SYNTAX INTEGER
                ACCESS read-write
                STATUS mandatory
                DESCRIPTION
                        ""
                ::= { gasEntry 9 }

        gasTotalTrial OBJECT-TYPE
                SYNTAX INTEGER
                ACCESS read-only
                STATUS mandatory
                DESCRIPTION
                        ""
                ::= { gasEntry 1001 }

        gasTotalFailed OBJECT-TYPE
                SYNTAX INTEGER
                ACCESS read-only
                STATUS mandatory
                DESCRIPTION
                        ""
                ::= { gasEntry 1002 }

        cntCount OBJECT-TYPE
                SYNTAX INTEGER
                ACCESS read-only
                STATUS mandatory
                DESCRIPTION
                        ""
                ::= { epCount 1 }

        cntTable OBJECT-TYPE
                SYNTAX SEQUENCE OF CntEntry
                ACCESS not-accessible
                STATUS deprecated
                DESCRIPTION
                        ""
                ::= { epCount 2 }

        cntEntry OBJECT-TYPE
                SYNTAX CntEntry
                ACCESS not-accessible
                STATUS deprecated
                DESCRIPTION
                        ""
                INDEX { cntID }
                ::= { cntTable 1 }

        CntEntry ::= SEQUENCE { 
            cntID DisplayString,
            cntType DisplayString,
            cntName DisplayString,
            cntSN DisplayString,
            cntState DisplayString,
            cntValue DisplayString,
            cntLastValue DisplayString,
            cntLastTime DisplayString,
            cntInitValue DisplayString
        }

        cntID OBJECT-TYPE
                SYNTAX DisplayString
                ACCESS read-only
                STATUS deprecated
                DESCRIPTION
                        ""
                ::= { cntEntry 1 }

        cntType OBJECT-TYPE
                SYNTAX DisplayString
                ACCESS read-only
                STATUS deprecated
                DESCRIPTION
                        ""
                ::= { cntEntry 2 }

        cntName OBJECT-TYPE
                SYNTAX DisplayString
                ACCESS read-write
                STATUS deprecated
                DESCRIPTION
                        ""
                ::= { cntEntry 3 }

        cntSN OBJECT-TYPE
                SYNTAX DisplayString
                ACCESS read-only
                STATUS deprecated
                DESCRIPTION
                        ""
                ::= { cntEntry 4 }

        cntState OBJECT-TYPE
                SYNTAX DisplayString
                ACCESS read-write
                STATUS deprecated
                DESCRIPTION
                        ""
                ::= { cntEntry 5 }

        cntValue OBJECT-TYPE
                SYNTAX DisplayString
                ACCESS read-write
                STATUS deprecated
                DESCRIPTION
                        ""
                ::= { cntEntry 6 }

        cntLastValue OBJECT-TYPE
                SYNTAX DisplayString
                ACCESS read-only
                STATUS deprecated
                DESCRIPTION
                        ""
                ::= { cntEntry 7 }

        cntLastTime OBJECT-TYPE
                SYNTAX DisplayString
                ACCESS read-only
                STATUS deprecated
                DESCRIPTION
                        ""
                ::= { cntEntry 8 }

        cntInitValue OBJECT-TYPE
                SYNTAX DisplayString
                ACCESS read-write
                STATUS deprecated
                DESCRIPTION
                        ""
                ::= { cntEntry 9 }

        prsCount OBJECT-TYPE
                SYNTAX INTEGER
                ACCESS read-only
                STATUS mandatory
                DESCRIPTION
                        ""
                ::= { epPressure 1 }

        prsTable OBJECT-TYPE
                SYNTAX SEQUENCE OF PrsEntry
                ACCESS not-accessible
                STATUS deprecated
                DESCRIPTION
                        ""
                ::= { epPressure 2 }

        prsEntry OBJECT-TYPE
                SYNTAX PrsEntry
                ACCESS not-accessible
                STATUS deprecated
                DESCRIPTION
                        ""
                INDEX { prsID }
                ::= { prsTable 1 }

        PrsEntry ::= SEQUENCE { 
            prsID DisplayString,
            prsType DisplayString,
            prsName DisplayString,
            prsSN DisplayString,
            prsState DisplayString,
            prsValue DisplayString,
            prsLastValue DisplayString,
            prsLastTime DisplayString,
            prsInitValue DisplayString
        }

        prsID OBJECT-TYPE
                SYNTAX DisplayString
                ACCESS read-only
                STATUS deprecated
                DESCRIPTION
                        ""
                ::= { prsEntry 1 }

        prsType OBJECT-TYPE
                SYNTAX DisplayString
                ACCESS read-only
                STATUS deprecated
                DESCRIPTION
                        ""
                ::= { prsEntry 2 }

        prsName OBJECT-TYPE
                SYNTAX DisplayString
                ACCESS read-write
                STATUS deprecated
                DESCRIPTION
                        ""
                ::= { prsEntry 3 }

        prsSN OBJECT-TYPE
                SYNTAX DisplayString
                ACCESS read-only
                STATUS deprecated
                DESCRIPTION
                        ""
                ::= { prsEntry 4 }

        prsState OBJECT-TYPE
                SYNTAX DisplayString
                ACCESS read-write
                STATUS deprecated
                DESCRIPTION
                        ""
                ::= { prsEntry 5 }

        prsValue OBJECT-TYPE
                SYNTAX DisplayString
                ACCESS read-write
                STATUS deprecated
                DESCRIPTION
                        ""
                ::= { prsEntry 6 }

        prsLastValue OBJECT-TYPE
                SYNTAX DisplayString
                ACCESS read-only
                STATUS deprecated
                DESCRIPTION
                        ""
                ::= { prsEntry 7 }

        prsLastTime OBJECT-TYPE
                SYNTAX DisplayString
                ACCESS read-only
                STATUS deprecated
                DESCRIPTION
                        ""
                ::= { prsEntry 8 }

        prsInitValue OBJECT-TYPE
                SYNTAX DisplayString
                ACCESS read-write
                STATUS deprecated
                DESCRIPTION
                        ""
                ::= { prsEntry 9 }

        dscCount OBJECT-TYPE
                SYNTAX INTEGER
                ACCESS read-only
                STATUS mandatory
                DESCRIPTION
                        ""
                ::= { epDiscrete 1 }

        dscTable OBJECT-TYPE
                SYNTAX SEQUENCE OF DscEntry
                ACCESS not-accessible
                STATUS deprecated
                DESCRIPTION
                        ""
                ::= { epDiscrete 2 }

        dscEntry OBJECT-TYPE
                SYNTAX DscEntry
                ACCESS not-accessible
                STATUS deprecated
                DESCRIPTION
                        ""
                INDEX { dscID }
                ::= { dscTable 1 }

        DscEntry ::= SEQUENCE { 
            dscID DisplayString,
            dscType DisplayString,
            dscName DisplayString,
            dscSN DisplayString,
            dscState DisplayString,
            dscValue DisplayString,
            dscLastValue DisplayString,
            dscLastTime DisplayString,
            dscInitValue DisplayString
        }

        dscID OBJECT-TYPE
                SYNTAX DisplayString
                ACCESS read-only
                STATUS deprecated
                DESCRIPTION
                        ""
                ::= { dscEntry 1 }

        dscType OBJECT-TYPE
                SYNTAX DisplayString
                ACCESS read-only
                STATUS deprecated
                DESCRIPTION
                        ""
                ::= { dscEntry 2 }

        dscName OBJECT-TYPE
                SYNTAX DisplayString
                ACCESS read-write
                STATUS deprecated
                DESCRIPTION
                        ""
                ::= { dscEntry 3 }

        dscSN OBJECT-TYPE
                SYNTAX DisplayString
                ACCESS read-only
                STATUS deprecated
                DESCRIPTION
                        ""
                ::= { dscEntry 4 }

        dscState OBJECT-TYPE
                SYNTAX DisplayString
                ACCESS read-write
                STATUS deprecated
                DESCRIPTION
                        ""
                ::= { dscEntry 5 }

        dscValue OBJECT-TYPE
                SYNTAX DisplayString
                ACCESS read-write
                STATUS deprecated
                DESCRIPTION
                        ""
                ::= { dscEntry 6 }

        dscLastValue OBJECT-TYPE
                SYNTAX DisplayString
                ACCESS read-only
                STATUS deprecated
                DESCRIPTION
                        ""
                ::= { dscEntry 7 }

        dscLastTime OBJECT-TYPE
                SYNTAX DisplayString
                ACCESS read-only
                STATUS deprecated
                DESCRIPTION
                        ""
                ::= { dscEntry 8 }

        dscInitValue OBJECT-TYPE
                SYNTAX DisplayString
                ACCESS read-write
                STATUS deprecated
                DESCRIPTION
                        ""
                ::= { dscEntry 9 }


        multiCount OBJECT-TYPE
                SYNTAX INTEGER
                ACCESS read-only
                STATUS deprecated
                DESCRIPTION
                        ""
                ::= { epMulti 1 }

        multiTable OBJECT-TYPE
                SYNTAX SEQUENCE OF DevEntry
                ACCESS not-accessible
                STATUS deprecated
                DESCRIPTION
                        ""
                ::= { epMulti 2 }

        multiEntry OBJECT-TYPE
                SYNTAX DevEntry
                ACCESS not-accessible
                STATUS deprecated
                DESCRIPTION
                        ""
                INDEX { multiID }
                ::= { multiTable 1 }

        MultiEntry ::= SEQUENCE { 
            multiID DisplayString,
            multiType DisplayString,
            multiName DisplayString,
            multiSN DisplayString,
            multiState DisplayString,
            multiValue DisplayString
        }

        multiID OBJECT-TYPE
                SYNTAX DisplayString
                ACCESS read-only
                STATUS deprecated
                DESCRIPTION
                        ""
                ::= { multiEntry 1 }

        multiType OBJECT-TYPE
                SYNTAX DisplayString
                ACCESS read-only
                STATUS deprecated
                DESCRIPTION
                        ""
                ::= { multiEntry 2 }

        multiName OBJECT-TYPE
                SYNTAX DisplayString
                ACCESS read-write
                STATUS deprecated
                DESCRIPTION
                        ""
                ::= { multiEntry 3 }

        multiSN OBJECT-TYPE
                SYNTAX DisplayString
                ACCESS read-only
                STATUS deprecated
                DESCRIPTION
                        ""
                ::= { multiEntry 4 }

        multiState OBJECT-TYPE
                SYNTAX DisplayString
                ACCESS read-write
                STATUS deprecated
                DESCRIPTION
                        ""
                ::= { multiEntry 5 }

        multiValue OBJECT-TYPE
                SYNTAX DisplayString
                ACCESS read-write
                STATUS deprecated
                DESCRIPTION
                        ""
                ::= { multiEntry 6 }


        ctrlCount OBJECT-TYPE
                SYNTAX INTEGER
                ACCESS read-only
                STATUS deprecated
                DESCRIPTION
                        ""
                ::= { epCtrl 1 }

        ctrlTable OBJECT-TYPE
                SYNTAX SEQUENCE OF DevEntry
                ACCESS not-accessible
                STATUS deprecated
                DESCRIPTION
                        ""
                ::= { epCtrl 2 }

        ctrlEntry OBJECT-TYPE
                SYNTAX DevEntry
                ACCESS not-accessible
                STATUS deprecated
                DESCRIPTION
                        ""
                INDEX { ctrlID }
                ::= { ctrlTable 1 }

        CtrlEntry ::= SEQUENCE { 
            ctrlID DisplayString,
            ctrlType DisplayString,
            ctrlName DisplayString,
            ctrlSN DisplayString,
            ctrlState DisplayString,
            ctrlValue DisplayString
        }

        ctrlID OBJECT-TYPE
                SYNTAX DisplayString
                ACCESS read-only
                STATUS deprecated
                DESCRIPTION
                        ""
                ::= { ctrlEntry 1 }

        ctrlType OBJECT-TYPE
                SYNTAX DisplayString
                ACCESS read-only
                STATUS deprecated
                DESCRIPTION
                        ""
                ::= { ctrlEntry 2 }

        ctrlName OBJECT-TYPE
                SYNTAX DisplayString
                ACCESS read-write
                STATUS deprecated
                DESCRIPTION
                        ""
                ::= { ctrlEntry 3 }

        ctrlSN OBJECT-TYPE
                SYNTAX DisplayString
                ACCESS read-only
                STATUS deprecated
                DESCRIPTION
                        ""
                ::= { ctrlEntry 4 }

        ctrlState OBJECT-TYPE
                SYNTAX DisplayString
                ACCESS read-write
                STATUS deprecated
                DESCRIPTION
                        ""
                ::= { ctrlEntry 5 }

        ctrlValue OBJECT-TYPE
                SYNTAX DisplayString
                ACCESS read-write
                STATUS deprecated
                DESCRIPTION
                        ""
                ::= { ctrlEntry 6 }

        smDiscovery OBJECT-TYPE
                SYNTAX INTEGER
                ACCESS read-write
                STATUS mandatory
                DESCRIPTION
                        ""
                ::= { epMgmt 1 }

        smDestroyDynamicObject OBJECT-TYPE
                SYNTAX DisplayString
                ACCESS read-write
                STATUS deprecated
                DESCRIPTION
                        ""
                ::= { epMgmt 2 }

        svrTable OBJECT-TYPE
                SYNTAX SEQUENCE OF SvrEntry
                ACCESS not-accessible
                STATUS deprecated
                DESCRIPTION
                        ""
                ::= { servers 1 }

        svrEntry OBJECT-TYPE
                SYNTAX SvrEntry
                ACCESS not-accessible
                STATUS deprecated
                DESCRIPTION
                        ""
                INDEX { svrIndex }
                ::= { svrTable 1 }

        SvrEntry ::= SEQUENCE { 
            svrIndex INTEGER,
            svrIpAddr IPAddress
        }

        svrIndex OBJECT-TYPE
                SYNTAX INTEGER
                ACCESS read-only
                STATUS deprecated
                DESCRIPTION
                        ""
                ::= { svrEntry 1 }

        svrIpAddr OBJECT-TYPE
                SYNTAX IPAddress
                ACCESS read-only
                STATUS deprecated
                DESCRIPTION
                        ""
                ::= { svrEntry 2 }

        logCount OBJECT-TYPE
                SYNTAX INTEGER
                ACCESS read-only
                STATUS deprecated
                DESCRIPTION
                        ""
                ::= { logs 1 }

        logTable OBJECT-TYPE
                SYNTAX SEQUENCE OF LogEntry
                ACCESS not-accessible
                STATUS deprecated
                DESCRIPTION
                        ""
                ::= { logs 2 }

        logEntry OBJECT-TYPE
                SYNTAX LogEntry
                ACCESS not-accessible
                STATUS deprecated
                DESCRIPTION
                        ""
                INDEX { logIndex }
                ::= { logTable 1 }

        LogEntry ::= SEQUENCE { 
            logIndex INTEGER,
            logTime DisplayString,
            logID DisplayString,
            logValue DisplayString,
            logLevel INTEGER,
            logString DisplayString
        }

        logIndex OBJECT-TYPE
                SYNTAX INTEGER
                ACCESS read-only
                STATUS deprecated
                DESCRIPTION
                        ""
                ::= { logEntry 1 }

        logTime OBJECT-TYPE
                SYNTAX DisplayString
                ACCESS read-only
                STATUS deprecated
                DESCRIPTION
                        ""
                ::= { logEntry 2 }

        logID OBJECT-TYPE
                SYNTAX DisplayString
                ACCESS read-only
                STATUS deprecated
                DESCRIPTION
                        ""
                ::= { logEntry 3 }

        logValue OBJECT-TYPE
                SYNTAX DisplayString
                ACCESS read-only
                STATUS deprecated
                DESCRIPTION
                        ""
                ::= { logEntry 4 }

        logLevel OBJECT-TYPE
                SYNTAX INTEGER
                ACCESS read-only
                STATUS deprecated
                DESCRIPTION
                        ""
                ::= { logEntry 5 }

        logString OBJECT-TYPE
                SYNTAX DisplayString
                ACCESS read-only
                STATUS deprecated
                DESCRIPTION
                        ""
                ::= { logEntry 6 }

        eventCount OBJECT-TYPE
                SYNTAX INTEGER
                ACCESS read-only
                STATUS mandatory
                DESCRIPTION
                        ""
                ::= { events 1 }

        eventTable OBJECT-TYPE
                SYNTAX SEQUENCE OF EventEntry
                ACCESS not-accessible
                STATUS deprecated
                DESCRIPTION
                        ""
                ::= { events 2 }

        eventCreate     OBJECT IDENTIFIER ::= { events 3 }

        eventDestroy    OBJECT IDENTIFIER ::= { events 4 }

        eventEntry OBJECT-TYPE
                SYNTAX EventEntry
                ACCESS not-accessible
                STATUS deprecated
                DESCRIPTION
                        ""
                INDEX { eventIndex }
                ::= { eventTable 1 }

        EventEntry ::= SEQUENCE { 
            eventIndex INTEGER,
            eventEPID DisplayString,
            eventLevel DisplayString,
            eventType DisplayString,
            eventCondition DisplayString
        }

        eventIndex OBJECT-TYPE
                SYNTAX INTEGER
                ACCESS read-only
                STATUS deprecated
                DESCRIPTION
                        ""
                ::= { eventEntry 1 }

        eventEPID OBJECT-TYPE
                SYNTAX DisplayString
                ACCESS read-only
                STATUS deprecated
                DESCRIPTION
                        ""
                ::= { eventEntry 2 }

        eventLevel OBJECT-TYPE
                SYNTAX DisplayString
                ACCESS read-only
                STATUS deprecated
                DESCRIPTION
                        ""
                ::= { eventEntry 3 }

        eventType OBJECT-TYPE
                SYNTAX DisplayString
                ACCESS read-only
                STATUS deprecated
                DESCRIPTION
                        ""
                ::= { eventEntry 4 }

        eventCondition OBJECT-TYPE
                SYNTAX DisplayString
                ACCESS read-write
                STATUS deprecated
                DESCRIPTION
                        ""
                ::= { eventEntry 5 }

        psType OBJECT-TYPE
                SYNTAX INTEGER
                ACCESS read-only
                STATUS mandatory
                DESCRIPTION
                        ""
                ::= { power 1 }

        psVoltageMax OBJECT-TYPE
                SYNTAX INTEGER
                ACCESS read-only
                STATUS mandatory
                DESCRIPTION
                        ""
                ::= { power 2 }

        psVoltageMin OBJECT-TYPE
                SYNTAX INTEGER
                ACCESS read-only
                STATUS mandatory
                DESCRIPTION
                        ""
                ::= { power 3 }

        trapServer      OBJECT IDENTIFIER ::= { traps 1 }

        tsCount OBJECT-TYPE
                SYNTAX INTEGER
                ACCESS read-only
                STATUS deprecated
                DESCRIPTION
                        ""
                ::= { trapServer 1 }

        tsTable OBJECT-TYPE
                SYNTAX SEQUENCE OF TsEntry
                ACCESS not-accessible
                STATUS deprecated
                DESCRIPTION
                        ""
                ::= { trapServer 2 }

        tsAdd OBJECT-TYPE
                SYNTAX DisplayString
                ACCESS read-write
                STATUS deprecated
                DESCRIPTION
                        ""
                ::= { trapServer 3 }

        tsDel OBJECT-TYPE
                SYNTAX DisplayString
                ACCESS read-write
                STATUS deprecated
                DESCRIPTION
                        ""
                ::= { trapServer 4 }

        tsEntry OBJECT-TYPE
                SYNTAX TsEntry
                ACCESS not-accessible
                STATUS deprecated
                DESCRIPTION
                        ""
                INDEX { tsIndex }
                ::= { tsTable 1 }

        TsEntry ::= SEQUENCE { 
            tsIndex INTEGER,
            tsIpAddr IPAddress
        }

        tsIndex OBJECT-TYPE
                SYNTAX INTEGER
                ACCESS read-only
                STATUS deprecated
                DESCRIPTION
                        ""
                ::= { tsEntry 1 }

        tsIpAddr OBJECT-TYPE
                SYNTAX IPAddress
                ACCESS read-only
                STATUS deprecated
                DESCRIPTION
                        ""
                ::= { tsEntry 2 }

        trapMsg         OBJECT IDENTIFIER ::= { traps 2 }

        msgDiscovery OBJECT-TYPE
                SYNTAX DisplayString
                ACCESS read-only
                STATUS deprecated
                DESCRIPTION
                        ""
                ::= { trapMsg 1 }

        msgAlert OBJECT-TYPE
                SYNTAX DisplayString
                ACCESS read-only
                STATUS deprecated
                DESCRIPTION
                        ""
                ::= { trapMsg 2 }

        adminOID OBJECT-TYPE
                SYNTAX DisplayString
                ACCESS read-write
                STATUS mandatory
                DESCRIPTION
                        ""
                ::= { admin 1 }

        adminMAC OBJECT-TYPE
                SYNTAX DisplayString
                ACCESS read-write
                STATUS mandatory
                DESCRIPTION
                        ""
                ::= { admin 2 }

        adminFactoryReset OBJECT-TYPE
                SYNTAX DisplayString
                ACCESS read-write
                STATUS mandatory
                DESCRIPTION
                        ""
                ::= { admin 3 }

        adminSystemTime OBJECT-TYPE
                SYNTAX DisplayString
                ACCESS read-write
                STATUS mandatory
                DESCRIPTION
                        ""
                ::= { admin 4 }

        adminReset OBJECT-TYPE
                SYNTAX DisplayString
                ACCESS read-write
                STATUS mandatory
                DESCRIPTION
                        ""
                ::= { admin 5 }

        adminDebug      OBJECT IDENTIFIER ::= { admin 100 }

        dbgBTTable OBJECT-TYPE
                SYNTAX SEQUENCE OF DbgBTEntry
                ACCESS not-accessible
                STATUS deprecated
                DESCRIPTION
                        ""
                ::= { adminDebug 1 }

        dbgBTEntry OBJECT-TYPE
                SYNTAX DbgBTEntry
                ACCESS not-accessible
                STATUS deprecated
                DESCRIPTION
                        ""
                INDEX { dbgBTIndex }
                ::= { dbgBTTable 1 }

        DbgBTEntry ::= SEQUENCE { 
            dbgBTIndex INTEGER,
            dbgBTTime DisplayString
        }

        dbgBTIndex OBJECT-TYPE
                SYNTAX INTEGER
                ACCESS read-only
                STATUS deprecated
                DESCRIPTION
                        ""
                ::= { dbgBTEntry 1 }

        dbgBTTime OBJECT-TYPE
                SYNTAX DisplayString
                ACCESS read-only
                STATUS deprecated
                DESCRIPTION
                        ""
                ::= { dbgBTEntry 2 }

    END
